module test-model-op-only {
    namespace "http://opendaylight.org/jsonrpc/test";
    prefix "test-model-op-only";
    organization "Lumina Networks";
    contact "Richard Kosegi <richard.kosegi@gmail.com>";

    revision 2018-03-05 {
        description "Initial revision";
    }

    container top-element {
        config false;
        leaf some-leaf {
            type int32;
        }

        container second-level {
            container third-level {
                leaf field5 {
                    type string;
                }
            }
        }
    }

    container items {
        list item {
            key "field1";
            leaf field1 {
                type int32;
            }
            leaf field2 {
                type string;
            }
            container subitem {
                leaf field3 {
                    type string;
                }
                list sublist {
                    leaf field4 {
                        type string;
                    }
                }
            }
        }

        list multikey-list {
            description "List to test composite key";
            key "field1 field2 field3";
            leaf field1 {
                type string;
            }
            leaf field2 {
                type int32;
            }
            leaf field3 {
                type string;
            }
        }
    }
}
