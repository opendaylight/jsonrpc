module test-model {
    namespace "urn:opendaylight:jsonrpc:test";
    prefix "tm";

    import ietf-inet-types {
        prefix "inet";
    }

    organization "Brocade";
    contact "Richard Kosegi <rkosegi@brocade.com>";
    description "Mock model to test various aspects of JSON-RPC ODL plugin";
    revision "2016-11-17";

    typedef watermark-value {
        description "Value of watermark";
        type int16;
    }

    grouping numbers-ll {
        leaf-list numbers {
            type int32;
        }
    }

    grouping numbers-list {
        list numbers {
            description "list of numbers";
            key "num";
            leaf "num" {
                type int32;
            }
        }
    }

    grouping watermark {
        leaf level {
            type watermark-value;
        }
    }

    grouping number-bucket {
        description "Dummy datastructure holding some numbers in it";
        container segment1 {
            description "Sub-container for leaf list data";
            uses numbers-list;
            uses watermark;
            container level2 {
                description "Arbitrary datastructure to test (de)serialization in JsonConverter";
                container level3 {
                    list inner-list {
                        key "item";
                        leaf item {
                            type union {
                                type int16;
                                type string;
                            }
                        }
                    }
                }
            }
        }
    }

    container top-element {
        uses number-bucket;
        container level2a {
            leaf abc {
                type string;
            }
        }
    }
    container grillconf {
        leaf gasKnob {
            config true;
            type uint32 {
                range "1..11";
            }
        }
    }

    rpc simple-method {
        description "Simplest RPC, no input, no output";
    }

    rpc multiply-ll {
        description "RPC with input and output data structures - using leaf-list.
                Multiplies each number in list by multuplier ";
        input {
            leaf multiplier {
                type int16;
            }
            uses numbers-ll;
        }
        output {
            uses numbers-ll;
        }
    }

    rpc method-with-anyxml {
        description "Arbitrary method which have anyxml as input";
        input {
            leaf some-number {
                type uint32;
            }
            anyxml some-data {
                description "Anyxml data";
            }
        }
    }

    rpc get-all-numbers {
        description "RPC method with no input but output";
        input {
        }
        output {
            uses number-bucket;
        }
    }

    rpc multiply-list {
        description "RPC with input and output data structures - using list. Multiplies
                each number in list by multuplier ";
        input {
            leaf multiplier {
                type int16;
            }
            uses numbers-list;
        }
        output {
            uses numbers-list;
        }
    }

    rpc error-method {
        description "This method will produce error in RPC handler";
    }

    rpc factorial {
        input {
            leaf in-number {
                type uint16;
            }
        }
        output {
            leaf out-number {
                type uint32;
            }
        }
    }

    rpc get-any-xml {
        description "Datastructure to test anyxml";
        input {
            leaf indata {
                type string;
            }
        }
        output {
            anyxml outdata {
            }
        }
    }

    identity drinks {
        description
                "Base for various coffee drinks";
    }

    identity coffee {
        base drinks;
    }

    rpc removeCoffeePot {
        description "Remove coffee from the brewer";
        output {
            leaf cups-brewed {
                type uint32 {
                    range "1 .. 6";
                }
                description "How many cups were brewed";
            }
            leaf drink {
                type identityref {
                    base drinks;
                }
                default 'coffee';
                description "Plain simple black coffee";
            }
        }
    }

    notification too-many-numbers {
        description "Alert when too many numbers are in deposit.";
        leaf current-level {
            type watermark-value;
        }
        leaf max-level {
            type watermark-value;
        }
    }

    list ipv4 {
        description "Top level list to test https://jira.opendaylight.org/browse/JSONRPC-9";
        key "name";
        leaf name {
            type string;
            description "The interfaces's name.";
        }
    }
}
