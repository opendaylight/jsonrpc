module jsonrpc-inband-models {
    namespace "urn:opendaylight:jsonrpc:ibm";
    prefix "ibm";
    import ietf-yang-types { prefix "yt"; revision-date 2013-07-15; }

    organization "Lumina Networks, Inc";
    description "YANG model of the JSON-RPC 2.0 inband models";

    revision "2019-01-12" {
        description "Initial revision";
    }

    grouping module {
        leaf name {
            description "Module identifier";
            type yt:yang-identifier;
        }
        leaf content {
            description "YANG module source";
            type string;
        }
    }

    rpc get-modules {
        description "Get list of all YANG modules required to mount this peer.";
        output {
            list modules {
                uses module;
                key name;
            }
        }
    }
}
